CCSDS-SLE-TRANSFER-SERVICE-ISP1-CREDENTIALS
DEFINITIONS
IMPLICIT TAGS
::= BEGIN

ISP1Credentials  ::= SEQUENCE
{ time         OCTET STRING (SIZE(8))  -- CCSDS CDS time code
, randomNumber INTEGER (0 .. 2147483647)
, theProtected OCTET STRING (SIZE(20..32)) -- It was 20 (SHA-1) until SLE version 3. SLE version 4 and later use SHA-256, which requires 32 bytes output
}

-- To be encoded using DER
HashInput ::= SEQUENCE
{ time OCTET STRING (SIZE(8))
, randomNumber INTEGER (0 .. 2147483647)
, userName VisibleString
, passWord OCTET STRING
}

END
