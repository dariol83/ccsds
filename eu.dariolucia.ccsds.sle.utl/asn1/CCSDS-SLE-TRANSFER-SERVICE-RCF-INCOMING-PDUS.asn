CCSDS-SLE-TRANSFER-SERVICE-RCF-INCOMING-PDUS
{iso identified-organization(3) standards-producing-organization(112)
    ccsds(4) space-link-extension(3) sle-transfer-services(1)
    modules(1) return-channel-frames-service(13) version-four(4)
    asn1-rcf-incoming-pdu(2)}

DEFINITIONS
IMPLICIT TAGS
::= BEGIN

IMPORTS     ConditionalTime
,           Credentials
,           InvokeId
    FROM CCSDS-SLE-TRANSFER-SERVICE-COMMON-TYPES
            SleScheduleStatusReportInvocation
,           SleStopInvocation
    FROM CCSDS-SLE-TRANSFER-SERVICE-COMMON-PDUS
            GvcId
,           RcfParameterName
    FROM CCSDS-SLE-TRANSFER-SERVICE-RCF-STRUCTURES
            SleBindInvocation
,           SleBindReturn
,           SlePeerAbort
,           SleUnbindInvocation
,           SleUnbindReturn
    FROM CCSDS-SLE-TRANSFER-SERVICE-BIND-TYPES
;

-- =============================================================
-- The first part of the module definition contains the RCF type
-- that contains all the possible PDUs the provider may receive.
-- =============================================================

RcfUserToProviderPdu            ::= CHOICE
{ rcfBindInvocation                 [100] SleBindInvocation
, rcfBindReturn                     [101] SleBindReturn
, rcfUnbindInvocation               [102] SleUnbindInvocation
, rcfUnbindReturn                   [103] SleUnbindReturn
, rcfStartInvocation                [0]   RcfStartInvocation
, rcfStopInvocation                 [2]   SleStopInvocation
, rcfScheduleStatusReportInvocation [4]   SleScheduleStatusReportInvocation
, rcfGetParameterInvocation         [6]   RcfGetParameterInvocation
, rcfPeerAbortInvocation            [104] SlePeerAbort
}

-- =============================================================
-- The second part of the module definition contains the types
-- used by the RCF-PDUs declared in the first part.
-- =============================================================

RcfGetParameterInvocation       ::= SEQUENCE
{   invokerCredentials                  Credentials
,   invokeId                            InvokeId
,   rcfParameter                        RcfParameterName
}

RcfStartInvocation              ::= SEQUENCE
{   invokerCredentials                  Credentials
,   invokeId                            InvokeId
,   startTime                           ConditionalTime
,   stopTime                            ConditionalTime
,   requestedGvcId                      GvcId
}

END
